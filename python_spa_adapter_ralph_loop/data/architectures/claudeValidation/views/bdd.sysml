/*
 * @view_type: bdd
 * @title: Automotive Domain Block Definition Diagram
 * @show_requirements: false
 * @show_ports: true
 * @show_attributes: false
 * @show_compositions: true
 */

import "../model.sysml";

package AutomotiveDomain_BDD {
    doc /*
        Block Definition Diagram View
        Architecture: claudeValidation
        Name: Electric Vehicle System Architecture
        Domain: Automotive

        This view shows the structural composition of the Electric Vehicle System,
        including all part definitions, port definitions, and the hierarchical
        relationships between components.
    */
}
