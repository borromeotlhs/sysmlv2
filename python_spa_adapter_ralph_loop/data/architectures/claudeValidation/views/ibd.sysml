/*
 * @view_type: ibd
 * @title: Electric Vehicle Internal Block Diagram
 * @context: AutomotiveDomain::ElectricVehicleSystem
 * @show_ports: true
 * @show_connections: true
 * @show_part_types: true
 * @layout_direction: TB
 */

import "../model.sysml";

package AutomotiveDomain_IBD {
    doc /*
        Internal Block Diagram View
        Architecture: claudeValidation
        Name: Electric Vehicle System Architecture
        Context: ElectricVehicleSystem

        This view shows the internal structure of the Electric Vehicle System,
        including all parts (instances), their ports, and the connections between them.
        The diagram focuses on:
        - Drivetrain subsystem with motor, transmission, differential, and wheels
        - Electrical power subsystem with battery, inverter, charging, and thermal management
        - Vehicle control unit coordinating all subsystems
        - All port-to-port connections showing data flow and power distribution
    */
}
