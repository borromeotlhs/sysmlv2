package arch_000013 {

    import ScalarValues::*;

    // Command Data Handling Reference Architecture 13
    // Domain: command data handling

    // Requirements
    public requirement REQ_001 {
        doc "The command data handling system shall exchange data through typed interfaces."
    }

    public requirement REQ_002 {
        doc "The command data handling system shall trace subsystem design to requirements."
    }

    public requirement REQ_003 {
        doc "The command data handling system shall provide fault detection and recovery."
    }

    // Port Definitions
    public port def CommandIF;
    public port def DiagnosticIF;
    public port def PowerIF;
    public port def StatusIF;

    // Component Definitions
    public part def MonitorInterface {
        attribute mass : Real [1];
        attribute power : Real [1];
        port sensorOut : CommandIF;
        port statusOut : DiagnosticIF;
        port configIn : CommandIF;
    }

    public part def DistributionSubsystem {
        attribute mass : Real [1];
        attribute power : Real [1];
        port telemetryOut : StatusIF;
    }

    public part def ProcessingProcessor {
        attribute processingPower : Real [1];
        attribute memorySize : Real [1];
        port ctrlIn : PowerIF;
    }

    public part def NavProcessor {
        attribute processingPower : Real [1];
        attribute memorySize : Real [1];
        port pwrIn : StatusIF;
    }

    // System Definition
    public part def CommandDataHandlingSystem {
        part monitorinterface : MonitorInterface {
            satisfy REQ_001;
            satisfy REQ_002;
        }
        part distributionsubsystem : DistributionSubsystem {
            satisfy REQ_003;
        }
        part processingprocessor : ProcessingProcessor {
        }
        part navprocessor : NavProcessor {
        }

        // Connections
        connect monitorinterface.statusOut to distributionsubsystem.telemetryOut;
        connect monitorinterface.configIn to distributionsubsystem.telemetryOut;
        connect monitorinterface.sensorOut to distributionsubsystem.telemetryOut;
        connect navprocessor.pwrIn to processingprocessor.ctrlIn;
    }

    // System Instance
    public part commanddatahandlingsystem : CommandDataHandlingSystem;

}
