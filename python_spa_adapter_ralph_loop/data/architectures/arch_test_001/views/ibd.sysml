// Import model definitions
import "model.sysml";

package arch_test_001_ibd {
    // View metadata
    doc /*
        Internal Block Diagram View
        Architecture: arch_test_001
        Name: Test Architecture 1
        Context: TestSystem
    */

    // View configuration (used by PlantUML generator)
    comment /*
        @viewType: InternalBlockDiagram
        @context: arch_test_001::TestSystem
        @showPorts: true
        @showConnections: true
        @showPartTypes: true
        @layoutDirection: TB
    */
}
