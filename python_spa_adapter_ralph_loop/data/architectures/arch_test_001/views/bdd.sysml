// Import model definitions
import "model.sysml";

package arch_test_001_bdd {
    // View metadata
    doc /*
        Block Definition Diagram View
        Architecture: arch_test_001
        Name: Test Architecture 1
    */

    // View configuration (used by PlantUML generator)
    comment /*
        @viewType: BlockDefinitionDiagram
        @showAttributes: true
        @showPorts: false
        @showCompositions: true
        @showRequirements: true
        @showSatisfyRelationships: true
    */
}
