package arch_000126 {

    import ScalarValues::*;

    // Data Processing Unit Reference Architecture 126
    // Domain: data processing unit

    // Requirements
    public requirement REQ_001 {
        doc "The data processing unit system shall exchange data through typed interfaces."
    }

    public requirement REQ_002 {
        doc "The data processing unit system shall trace subsystem design to requirements."
    }

    // Port Definitions
    public port def CommandIF;
    public port def ControlIF;
    public port def DataIF;
    public port def DiagnosticIF;
    public port def SignalIF;
    public port def StatusIF;
    public port def TelemetryIF;

    // Component Definitions
    public part def CommProcessor {
        attribute processingPower : Real [1];
        attribute memorySize : Real [1];
        port pwrIn : DataIF;
        port cmdIn : DataIF;
    }

    public part def MonitorPayload {
        attribute dataRate : Real [1];
        attribute resolution : Real [1];
        port configIn : SignalIF;
    }

    public part def FlightProcessor {
        attribute processingPower : Real [1];
        attribute memorySize : Real [1];
        port cmdIn : TelemetryIF;
        port dataIn : CommandIF;
    }

    public part def SensorSubsystem {
        attribute dataRate : Real [1];
        attribute resolution : Real [1];
        port telemetryOut : StatusIF;
    }

    public part def DataActuator {
        attribute mass : Real [1];
        attribute power : Real [1];
        port dataIn : ControlIF;
        port statusOut : DiagnosticIF;
    }

    public part def MonitorController {
        attribute processingPower : Real [1];
        attribute memorySize : Real [1];
        port sensorOut : TelemetryIF;
    }

    // System Definition
    public part def DataProcessingUnitSystem {
        part commprocessor : CommProcessor {
        }
        part monitorpayload : MonitorPayload {
        }
        part flightprocessor : FlightProcessor {
        }
        part sensorsubsystem : SensorSubsystem {
            satisfy REQ_002;
        }
        part dataactuator : DataActuator {
            satisfy REQ_001;
        }
        part monitorcontroller : MonitorController {
        }

        // Connections
        connect commprocessor.cmdIn to monitorcontroller.sensorOut;
        connect commprocessor.pwrIn to dataactuator.dataIn;
        connect flightprocessor.dataIn to dataactuator.dataIn;
        connect commprocessor.cmdIn to sensorsubsystem.telemetryOut;
        connect dataactuator.statusOut to flightprocessor.dataIn;
    }

    // System Instance
    public part dataprocessingunitsystem : DataProcessingUnitSystem;

}
