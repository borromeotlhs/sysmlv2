// Import model definitions
import "model.sysml";

package test_arch_001_bdd {
    // View metadata
    doc /*
        Block Definition Diagram View
        Architecture: test_arch_001
        Name: Simple Test Architecture
    */

    // View configuration (used by PlantUML generator)
    comment /*
        @viewType: BlockDefinitionDiagram
        @showAttributes: true
        @showPorts: false
        @showCompositions: true
        @showRequirements: true
        @showSatisfyRelationships: true
    */

    // Views reference elements from imported package
    // The model elements are not redeclared here
}
