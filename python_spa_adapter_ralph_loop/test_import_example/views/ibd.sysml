// Import model definitions
import "../model.sysml";

package test_arch_001_ibd {
    // View metadata
    doc /*
        Internal Block Diagram View
        Architecture: test_arch_001
        Name: Simple Test Architecture
        Context: TestSystem
    */

    // View configuration (used by PlantUML generator)
    comment /*
        @viewType: InternalBlockDiagram
        @context: test_arch_001::TestSystem
        @showPorts: true
        @showConnections: true
        @showPartTypes: true
        @layoutDirection: TB
    */
}
