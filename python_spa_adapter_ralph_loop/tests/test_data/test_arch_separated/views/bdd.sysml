/*
 * @viewType: BlockDefinitionDiagram
 * @showAttributes: true
 * @context: test_arch_sep::SeparatedSystem
 */

import "model.sysml";

package test_arch_sep_bdd {
    // BDD View - imports from model
}
