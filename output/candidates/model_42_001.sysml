package model_42_001 {
    part def SensorSystem605 {
        part powersubsystem239 : SensorModule028;
    }

    part def SensorModule028;

    part def FlightController666;

    part def BatteryModule430;

    requirement def PerformanceRequirement76 {
        doc /* The performance shall meet operational requirements. */
    }
}
